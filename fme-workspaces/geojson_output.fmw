FME workspace geojson_output.fmw

Parameters:
- DestDataset_GEOJSON = tmp.geojson   # Destination GeoJSON File
- SourceDataset_SHAPE = /Users/alexanno/www/github-repo/FME-WT-livecoding-restapi/fme-workspaces/polygons_fme.shp   # Source Esri Shape File(s)

Readers:
- SHAPE_1: SHAPE from $(SourceDataset_SHAPE)

Writers:
- GEOJSON_1: GEOJSON to $(DestDataset_GEOJSON)

polygons_fme (reader SHAPE_1)
    attributes: id number(10,0), data char(80)
    -> NewFeatureType (writer GEOJSON_1)
NewFeatureType (writer GEOJSON_1)
